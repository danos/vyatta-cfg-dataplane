module vyatta-system-hugepages-v1 {
	namespace "urn:vyatta.com:mgmt:vyatta-system-hugepages-v1:1";
	prefix vyatta-system-hugepages-v1;

	import configd-v1 {
		prefix configd;
	}
	import vyatta-system-v1 {
		prefix system;
	}

	organization "AT&T Inc.";
	contact
		"AT&T
		 Postal: 208 S. Akard Street
		         Dallas, TX 25202
		 Web: www.att.com";

	description
		"Copyright (c) 2018, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Vyatta system memory yang file to configure hugepages at boot";

	revision 2018-09-04 {
		description "Initial revision.";
	}

	grouping hugepages-group {
		description "System hugepages parameters";
		container hugepages {
			description "Parameters used as hints to huge pages reservation at system" +
				    " boot. These hints may be ignored when it is larger than total" +
				    " memory or smaller than the minimum platform requirements.";
			presence "Huge pages hints configured";
			configd:end "/opt/vyatta/share/tmplscripts/system/hugepages/update-hugepages";
			must "(not(dataplane) or (dataplane <= reserved))" {
				error-message "You cannot reserve more hugepages for dataplane than the total hugepages reserved";
			}
			leaf reserved {
				description "Total Hugepages Memory in MB Reserved at system boot. Includes dataplane hugepages.";
				configd:help "Total Hugepages Memory in MB Reserved at system boot. Includes dataplane hugepages.";
				mandatory true;
				type uint32 {
					range "512..1048576";
				}
				units "megabytes";
			}
			leaf dataplane {
				description "Hugepages memory reserved for Dataplane in MB";
				configd:help "Hugepages memory reserved for Dataplane in MB";
				type uint32 {
					range "512..131072";
				}
				units "megabytes";
			}
		}
	}

	augment /system:system {
		uses hugepages-group;
	}
}
