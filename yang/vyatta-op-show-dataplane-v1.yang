module vyatta-op-show-dataplane-v1 {
	namespace "urn:vyatta.com:mgmt:vyatta-op-show-dataplane:1";
	prefix vyatta-op-show-dataplane-v1;

	import vyatta-types-v1 {
		prefix types;
	}
	import vyatta-opd-extensions-v1 {
		prefix opd;
	}
	import vyatta-op-show-v1 {
		prefix show;
	}

	organization "AT&T Inc.";
	contact
		"AT&T
		 Postal: 208 S. Akard Street
		         Dallas, TX 75202, USA
		 Web: www.att.com";

	description
		"Copyright (c) 2019-2021, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		Defines the top 'dataplane' level under 'show' for operational CLI";

	revision 2021-09-24 {
		description "Add show dataplane route next-hop statistics.";
	}

	revision 2021-06-24 {
		description "Add a show command for 'dataplane arp'.";
	}

	revision 2020-11-16 {
		description "Add a show command for 'dataplane feature'.";
	}

	revision 2020-07-10 {
		description "Add a show command for 'dataplane statistics'.";
	}

	revision 2020-01-17 {
		description "Add a show command for 'dataplane plugin feature'";
	}

	revision 2019-05-20 {
		description "Initial version";
	}

	grouping route-nexthop-group {
		opd:command next-hop {
			opd:help "Show IP route next hop statistics";
			opd:argument address {
				opd:help "Show IP route next hop statistics";
				opd:on-enter "vplane-route.pl --next-hop $5";
				type types:ipv4-address;
			}
		}
	}

	grouping route6-nexthop-group {
		opd:command next-hop {
			opd:help "Show IPv6 route next hop statistics";
			opd:argument address {
				opd:help "Show IPv6 route next hop statistics";
				opd:on-enter "vplane-route.pl --v6 --next-hop $5";
				type types:ip-address;
			}
		}
	}

	opd:augment /show:show {
		opd:command dataplane {
			opd:help "Show dataplane information";
			opd:privileged true;
			opd:on-enter "vplane-monitor.pl";

			opd:command plugin {
				opd:help "Show dataplane plugin information";
				opd:privileged true;

				opd:command feature {
					opd:help "Show dataplane feature plugin information";
					opd:privileged true;
					opd:on-enter "vyatta-op-dataplane-plugin";
				}
			}

			opd:command feature {
				opd:help "Show dataplane feature information";

				opd:repeatable true;
				opd:inherit "" {
					opd:on-enter "vyatta-op-dataplane-feature ${@:4}";
				}
				opd:option interface {
					opd:help "Show features for a specific interface";
					opd:allowed "echo all; vyatta-interfaces.pl --show dataplane";
					type string;
				}
				opd:option vrf {
					opd:help "Show features for a specific routing-instance";
					opd:allowed 'echo all; echo default; getvrflist --name-only';
					type string;
				}
				opd:command global {
					opd:help "Show global features";
				}
				opd:command ip {
					opd:help "Show IP features";
				}
 				opd:command ip6 {
					opd:help "Show IPv6 features";
				}
				opd:command l2 {
					opd:help "Show layer 2 features";
				}
				opd:command sparse {
					opd:help "Do not show empty feature node points";
				}
				opd:option filter {
					opd:help "Show features matching a sub-string";
					type string;
				}
			}

			opd:command route {
				opd:help "Show dataplane FIB table";
				opd:on-enter "vplane-route.pl";
				uses route-nexthop-group;
				opd:option routing-instance {
					opd:help "Show dataplane routing-instance information";
					opd:allowed 'getvrflist --name-only';
					opd:on-enter "vplane-route.pl --routing-instance $5";
					type string;
					uses route-nexthop-group {
						refine next-hop/address {
							opd:on-enter "vplane-route.pl --next-hop $7 --routing-instance $5";
						}
					}
				}
			}

			opd:command route6 {
				opd:help "Show dataplane FIB IPv6 table";
				opd:on-enter "vplane-route.pl --v6";
				uses route6-nexthop-group;
				opd:option routing-instance {
					opd:help "Show dataplane routing-instance information";
					opd:allowed 'getvrflist --name-only';
					opd:on-enter "vplane-route.pl --v6 --routing-instance $5";
					type string;
					uses route6-nexthop-group {
						refine next-hop/address {
							opd:on-enter "vplane-route.pl --v6 --next-hop $7 --routing-instance $5";
						}
					}
				}
			}

			opd:command statistics {
				opd:help "Show dataplane statistics";
			}
			
		    opd:command arp {
			    opd:help "Show dataplane ARP table";
		        opd:on-enter "vplane-arp arp";
			
			    opd:argument ifname {
                    opd:help "Show dataplane ARP table for a specific interface";
                    opd:allowed "vyatta-interfaces.pl --show dataplane,vhost,bonding,bridge,switch";
                    type string;
                    opd:on-enter "vplane-arp --show-intf $4 arp";

                    opd:argument address {
                            opd:help "Show dataplane ARP entry for a specific address";
                            type string{
                                opd:pattern-help "<x.x.x.x>";
                            }
                            opd:on-enter "vplane-arp --show-intf $4 --addr $5 arp";
                    }
                }
			}
		}
	}
}
