module vyatta-op-show-platform-dataplane-v1 {
	namespace "urn:vyatta.com:mgmt:vyatta-op-show-platform-dataplane:1";
	prefix vyatta-op-show-platform-dataplane-v1;

	import vyatta-opd-extensions-v1 {
		prefix opd;
	}
	import vyatta-op-show-v1 {
		prefix show;
	}
	import vyatta-op-show-platform-v1 {
		prefix pd;
	}

	organization "AT&T Inc.";
	contact
		"AT&T
		 Postal: 208 S. Akard Street
		         Dallas, TX 25202
		 Web: www.att.com";

	description
		"Copyright (c) 2018-2019, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		Defines the 'dataplane' level under 'show platform' for operational CLI";

	revision 2020-02-24 {
		description "Add command for mpls-route";
	}

	revision 2019-05-13 {
		description "added commands for features mroute and mroute6";
	}

	revision 2018-07-10 {
		description "Initial version";
	}

	grouping dataplane-subset {
		opd:command error {
			opd:help "Show objects that had errors while programming in HW";
			opd:on-enter 'vyatta-show-platform-dataplane.py --obj=$4 --subset=error';
		}
		opd:command partial {
			opd:help "Show objects that are partially programmed in HW";
			opd:on-enter 'vyatta-show-platform-dataplane.py --obj=$4 --subset=partial';
		}
		opd:command not-needed {
			opd:help "Show objects that are not needed in HW";
			opd:on-enter 'vyatta-show-platform-dataplane.py --obj=$4 --subset=not_needed';
		}
		opd:command no-resource {
			opd:help "Show objects that HW did not have resources for";
			opd:on-enter 'vyatta-show-platform-dataplane.py --obj=$4 --subset=no_resource';
		}
		opd:command no-support {
			opd:help "Show objects that there is no support for";
			opd:on-enter 'vyatta-show-platform-dataplane.py --obj=$4 --subset=no_support';
		}
	}

	opd:augment /show:show/pd:platform {
		opd:command dataplane {
			opd:help "Show system platform dataplane information";
			opd:on-enter 'vyatta-show-platform-dataplane.py';

			opd:command route {
				opd:help "Show system platform dataplane route";
				opd:on-enter 'vyatta-show-platform-dataplane.py --obj=route';

				uses dataplane-subset;
			}
			opd:command route6 {
				opd:help "Show system platform dataplane route6";
				opd:on-enter 'vyatta-show-platform-dataplane.py --obj=route6';

				uses dataplane-subset;
			}
			opd:command mroute {
				opd:help "Show system platform dataplane multicast route";
				opd:on-enter 'vyatta-show-platform-dataplane.py --obj=mroute';

				uses dataplane-subset;
			}
			opd:command mroute6 {
				opd:help "Show system platform dataplane IPv6 multicast route";
				opd:on-enter 'vyatta-show-platform-dataplane.py --obj=mroute6';

				uses dataplane-subset;
			}
			opd:command mpls-route {
				opd:help "Show system platform dataplane MPLS route";
				opd:on-enter 'vyatta-show-platform-dataplane.py --obj=mpls-route';

				uses dataplane-subset;
			}
		}
	}
}
