module vyatta-op-storm-control-v1 {
	namespace "urn:vyatta.com:mgmt:vyatta-op-storm-control:1";
	prefix vyatta-op-storm-control-v1;

	import vyatta-opd-extensions-v1 {
		prefix opd;
	}
	import vyatta-op-show-v1 {
		prefix show;
	}
	import vyatta-op-clear-v1 {
		prefix clear;
	}
	import vyatta-interfaces-dataplane-v1 {
		prefix if-dp;
	}

	organization "AT&T Inc.";
	contact
		"AT&T
		 Postal: 208 S. Akard Street
		         Dallas, TX 75202.
		         USA
		 Web: www.att.com";

	description
		"Copyright (c) 2018-2020, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		Commands for displaying storm control status & counters";

	revision 2020-11-05 {
		description "Add ability to show policies, show stats and clear stats by specifying a vif";
	}
	revision 2019-01-11 {
		description "Change interface node to be an option";
	}
	revision 2018-07-13 {
		description "Initial version";
	}

	opd:augment /show:show {
		opd:command storm-control {
			opd:help "Show storm-control information";

			opd:command policies {
				opd:help "Show storm-control policies";
				opd:on-enter "vplane-op-storm-control --action show --object policies ";

				opd:option interface {
					opd:help "Show storm-control statistics on specified interface";
					opd:allowed "vyatta-interfaces.pl --show=dataplane";
					opd:on-enter "vplane-op-storm-control --action show --object policies --dev $5";
					type union {
						type if-dp:dataplane-ifname;
						type if-dp:dataplane-vifname;
					}
				}
			}

			opd:command statistics {
				opd:help "Show storm-control statistics";
				opd:on-enter "vplane-op-storm-control --action show --object stats";

				opd:option interface {
					opd:help "Show storm-control statistics on specified interface";
					opd:allowed "vyatta-interfaces.pl --show=dataplane";
					opd:on-enter "vplane-op-storm-control --action show --object stats --dev $5";
					type union {
						type if-dp:dataplane-ifname;
						type if-dp:dataplane-vifname;
					}
				}
			}
		}
	}

	opd:augment /clear:clear {
		opd:command storm-control {
			opd:help "Clear storm-control information";

			opd:command statistics {
				opd:help "Clear storm-control statistics";
				opd:on-enter "vplane-op-storm-control --action clear --object stats ";

				opd:option interface {
					opd:help "Clear storm-control statistics on specified interface";
					opd:allowed "vyatta-interfaces.pl --show=dataplane";
					opd:on-enter "vplane-op-storm-control --action clear --object stats --dev $5";
					type union {
						type if-dp:dataplane-ifname;
						type if-dp:dataplane-vifname;
					}
				}
			}
		}
	}

}
