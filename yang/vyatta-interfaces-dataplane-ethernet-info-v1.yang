module vyatta-interfaces-dataplane-ethernet-info-v1 {
    namespace "urn:vyatta.com:mgmt:vyatta-interfaces-dataplane-ethernet-info:1";
    prefix "vyatta-interfaces-dataplane-ethernet-info-v1";

    import configd-v1 {
         prefix configd;
    }

    import vyatta-types-v1 {
        prefix types;
    }

    import vyatta-interfaces-dataplane-v1 {
        prefix dp;
    }

    organization "AT&T Inc.";
    contact
        "AT&T
         Postal: 208 S. Akard Street
         Dallas, TX 75202
         Web: www.att.com";

    description
        "Copyright (c) 2020, AT&T Intellectual Property.
         All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

        Licensed under the Apache License, Version 2.0 (the License) which is available at
        http://www.apache.org/licenses/LICENSE-2.0

        Ethernet information for dataplane interfaces.";

    revision 2020-10-10 {
        description "Add Platform State to the ethernet info group.";
    }

    revision 2020-09-10 {
        description "Initial revision of version 1.";
    }

    typedef port-name {
        description "The name of the port";
        type types:alpha-numeric {
            configd:help "Port name";
        }
    }

    grouping eth-info-grp {
        description
            "Operational state of the interface";

        container ethernet-info {
            leaf pause-frame {
                description
                    "Enable or Disable TX/RX pause frames on interface.";
                configd:help "Enable or Disable TX/RX pause frames on interface";
                type dp:pause-mode;
            }
            leaf platform-state {
                description "Platform state for the given interface";
                type string;
            }
        }
    }

    rpc eth-info {
        configd:call-rpc "/opt/vyatta/sbin/vyatta-ethernet-info --action=eth-info";

        description
            "Retrieve ethernet information for a physical interface.";

        input {
            leaf name {
                description "Interface for which to get ethernet info";
                mandatory true;
                type port-name;

            }
        }
        output {
            uses  eth-info-grp;
        }
    }
}
