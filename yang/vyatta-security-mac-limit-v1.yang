module vyatta-security-mac-limit-v1 {
	namespace "urn:vyatta.com:mgmt:vyatta-security-mac-limit:1";
	prefix vyatta-security-mac-limit-v1;

	import vyatta-security-v1 {
		prefix security;
	}

	import vyatta-interfaces-v1 {
		prefix if;
	}

	import vyatta-interfaces-dataplane-v1 {
		prefix dp;
	}

	import vyatta-interfaces-dataplane-switch-v1 {
		prefix dp-sw;
	}

	import vyatta-interfaces-switch-v1 {
		prefix sw;
	}

	import configd-v1 {
		prefix configd;
	}

	organization "AT&T Inc.";
	contact
		"AT&T
		 Postal: 208 S. Akard Street
		         Dallas, TX 75202
		 Web: www.att.com";

	description
		"Copyright (c) 2020-2021, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 YANG module for Vyatta mac limit";

	revision 2021-03-16 {
		description "Updated description.";
	}

	revision 2020-05-14 {
		description "Initial version.";
	}

	feature mac-limiting {
		description "Enable limiting of MACs per port per vlan";
	}

	augment /security:security {
		container mac-limit {
		    if-feature mac-limiting;
			description "MAC limit";
			configd:help "MAC limit";

			list profile {
				description "MAC limit profile configuration.
				             Defines the constraints applied to the number of MACs permitted.";
				configd:help "MAC limit profile configuration.";

				key "profile-name";
				leaf profile-name {
					type string;
					description "Name of mac limit profile";
					configd:help "Name of mac limit profile";
				}

				leaf limit {
					description "Maximum number of MACs permitted";
					configd:help "Maximum number of MACs permitted";
					type uint32 {
						range 1..131072;
					}
					configd:update "/opt/vyatta/sbin/vyatta-mac-limit --cmd profile --profile $VAR(../@) --action SET --update $VAR(.)";
					configd:delete "/opt/vyatta/sbin/vyatta-mac-limit --cmd profile --profile $VAR(../@) --action DELETE --update $VAR(.)";
				}
			}
		}
	}

	augment /if:interfaces/dp:dataplane/dp-sw:switch-group/dp-sw:port-parameters/dp-sw:vlan-parameters {
		container mac-limit {
			if-feature mac-limiting;
			list vlan {
				key "vlan-id";
				leaf vlan-id {
					type sw:vlan-id;
				}
				leaf profile {
					 type leafref {
						 path "/security:security/mac-limit/profile/profile-name";
				     }
					 description "MAC limit profile name";
					 configd:help "MAC limit profile name";
					 configd:update "vyatta-mac-limit --cmd profile --dev $VAR(../../../../../../@) --vlan $VAR(../@) --action SET --profile $VAR(@)";
					 configd:delete "vyatta-mac-limit --cmd profile --dev $VAR(../../../../../../@) --vlan $VAR(../@) --action DELETE --profile $VAR(@)";
				}
			}
			configd:help "MAC address limit parameters for the VLAN";
			description "MAC address limit parameters for the VLAN";
		}
	}

}
