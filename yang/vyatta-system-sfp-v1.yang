module vyatta-system-sfp-v1 {
	namespace "urn:vyatta.com:mgmt:vyatta-system-sfp:1";
	prefix vyatta-system-sfp-v1;

	import vyatta-system-v1 {
		prefix system;
	}
	import vyatta-types-v1 {
		prefix types;
	}
	import configd-v1 {
		prefix configd;
	}

	organization "AT&T Inc.";
	contact
		"AT&T
		 Postal: 208 S. Akard Street
		         Dallas, TX 75202
		 Web: www.att.com";

	description
		"Copyright (c) 2021, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Package management configuration";

	revision 2021-09-28 {
		description "Added an RPC for retrieving SFP permit list status info";
	}

	revision 2021-08-25 {
		description "Add SFP permit-list configuration";
	}
	revision 2021-06-20 {
		description "Initial revision of SFP monitoring
				and configuration";
	}

	feature sfp-permit-list {
		description "Enable SFP permit lists of inserted transceiver modules";
	}

	grouping sfp-properties {
		description
			"SFP transceiver properties";

		leaf vendor {
			type string {
				length 1..16;
			}
			description
				"The full name of the SFP transceiver vendor, up to 16 ASCII characters";
		}

		leaf oui {
			type string {
				pattern '[0-9a-f]{2,2}\.[0-9a-f]{2,2}\.[0-9a-f]{2,2}';
			}
			description
				"The SFP transceiver vendor's organizationally unique identifier
				field (vendor OUI) is a 3-byte field that contains the IEEE Company
				Identifier for the vendor. A value of all zero in the 3-byte field
				indicates that the Vendor OUI is unspecified. It is represented here
				as a hexadecimal string with a '.' between consecutive bytes";
			reference
				"https://en.wikipedia.org/wiki/Organizationally_unique_identifier
				http://standards-oui.ieee.org/oui/oui.txt";
		}

		leaf part {
			type string {
				pattern '[0-9a-zA-Z_\-]{1,15}[0-9a-zA-Z_\-\*]{0,1}';
			}
			description
				"The SFP transceiver vendor's part number, up to 16 ASCII characters";
		}

		leaf revision {
			type string {
				length 1..4;
			}
			description
				"The SFP transceiver vendor's revision number, up to 4 ASCII characters";
		}
	}

	grouping sfp-status {
		description
			"Permit list status information for a SFP transceiver";

		leaf interface-name {
			description "Name of the SFP transceiver interface";
			type types:interface-ifname;
		}

		leaf detection-time {
			type string {
				length 1..20;
			}
			description
				"SFP transceiver time of detection in seconds since boot";
		}

		leaf state {
			description "SFP transceiver permit list approval";
			type enumeration {
				enum approved {
					description "SFP transceiver in the permit list";
				}
				enum unapproved {
					description "SFP transceiver not in the permit list";
				}
			}
		}

		leaf action {
			description "Action performed on the SFP transceiver";
			type enumeration {
				enum disabled {
					description "SFP transceiver disabled";
				}
				enum enabled {
					description "SFP transceiver enabled";
				}
			}
		}

		uses sfp-properties;
	}

	augment /system:system {
		container sfp {
			presence "Enable SFP features";
			configd:help "SFP monitoring parameters";
			description "SFP monitoring and permit list configuration and control";

			container permit {
				if-feature sfp-permit-list;
				presence "Enable SFP permit";
				configd:help "Configure allowed SFPs and action taken in case of a mismatch";
				description
					"Network platforms can support a wide variety SFP transceiver modules.
					However sometimes it is prefered that only certified or validated SFP
					transceiver modules are installed on certain network platforms. SFP permit
					lists allow the configuration of lists of SFP transceiver modules that
					are supported in the system.";
				must "mismatch-action/enforcement/state = 'disabled' or count(list)>0 or not(mismatch-action/enforcement/state)" {
					error-message "SFP permit list must not be empty when enforcement is enabled";
				}

				list list {
					configd:help "List of allowed SFP transceiver modules";
					configd:end "vyatta-sfp-permit-list --list $VAR(@)";
					description
						"This list contains details about SFP transceiver modules that are
						certified or validated on this platform.";
					key "name";

					leaf name {
						type types:alpha-numeric {
							length 1..64;
							configd:help "Name of the permit list";
						}
						description "Name given to the permit list";
					}

					list index {
						key "index";
						leaf index {
							configd:help "Identifier for entry";
							description "Identifier for entry";
							type uint32 {
								range 1..1000;
								configd:help "Identifier for entry";
							}
						}

						uses sfp-properties {

							refine vendor {
								configd:help "Full name of SFP transceiver vendor";
							}

							refine oui {
								configd:help "Vendor organizationally unique identifier field (vendor OUI)";
							}

							refine part {
								configd:help "SFP Vendor-Part ID";
								description
									"The SFP transceiver vendor's part number, up to 16 ASCII characters
									 A wildcard character ('*'), is allowed as the last (right-most)
									 character";
								mandatory true;
							}

							refine revision {
								configd:help "SFP Transceiver vendor's revision number";
							}
						}
					}
				}

				container mismatch-action {
					configd:end "vyatta-sfp-permit-list --mismatch $VAR(@)";
					description "Permit list validation failure control";
					configd:help "Action on permit list failure.";

					leaf logging {
						description "Logging preference";
						configd:help "Logging preference";
						type enumeration {
							enum "disabled" {
								description "Disable insertion SFP logging";
								configd:help "Disable insertion SFP logging";
							}
							enum "enabled" {
								description "Enable insertion SFP logging";
								configd:help "Enable insertion SFP logging";
							}
						}
						default "enabled";
					}

					container enforcement {
						description "SFP enforcement mode parameters";
						configd:help "SFP enforcement mode parameters";
						leaf state {
							configd:help "Toggle SFP permit list activation";
							description
								"Enable or disable SFP permit lists. If enabled inserted SFP will be
								validated against the configured permit lists.";
							type enumeration {
								enum disabled {
									description "Disable SFP enforcement";
									configd:help "Disable SFP enforcement";
								}
								enum enabled {
									description "Enable SFP enforcement";
									configd:help "Enable SFP enforcement";
								}
							}
							default "disabled";
						}
					}
				}
			}
		}
	}

	rpc get-sfp-permit-list-status {
		configd:call-rpc "/opt/vyatta/bin/vplane-sfp-permit-list --status";

		description "Retrieves SFP permit list status information";

		input {
			leaf interface-name {
				description "Name of the SFP transceiver interface";
				type types:interface-ifname;
			}
		}

		output {
			leaf enforcement-mode {
				description "SFP permit list enforcement mode";
				type enumeration {
					enum disabled {
						description "SFP permit list enforcement disabled";
					}
					enum enabled {
						description "SFP permit list enforcement enabled";
					}
				}
			}

			list sfp-list {
				key "interface-name";
				description "Permit list status information for a list of SFPs";
				uses sfp-status;
			}
		}
	}
}
