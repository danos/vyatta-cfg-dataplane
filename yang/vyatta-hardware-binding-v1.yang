module vyatta-hardware-binding-v1 {
	namespace "urn:vyatta.com:mgmt:vyatta-hardware-binding:1";
	prefix vyatta-hardware-binding-v1;

	import configd-v1 {
		prefix configd;
	}
	import vyatta-types-v1 {
		prefix types;
	}

	organization "Brocade Communications Systems, Inc.";
	contact
		"Brocade Communications Systems, Inc.
		 Postal: 130 Holger Way
		         San Jose, CA 95134
		 E-mail: support@Brocade.com
		 Web: www.brocade.com";

	description
		"Copyright (c) 2017, AT&T Intellectual Property. All rights reserved.
		 Copyright (c) 2017 by Brocade Communication Systems, Inc.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Vyatta dataplane interface hardware binding configuration";

	revision 2017-07-04 {
		description "Initial revision for version 1";
	}

	grouping hardware-parameters {
		container hardware {
			presence "Enable hardware binding";
			configd:help "Hardware binding override";
			description "Used to bind an interface to specific PCI hardware";

			must "(count(firmware-index) + count(mac) + count(pci-address) + count(pci-slot) + count(port)) = 1" {
				error-message "Only one of 'firmware-index', 'mac', 'pci-address', 'pci-slot', or 'port' may be set";
			}

			leaf firmware-index {
				type uint32;
				description "Used to match this interface by the ACPI index assigned by the BIOS to an onboard PCI device";
				configd:help "Index assigned by BIOS for onboard device";
			}
			leaf mac {
				type types:mac-address;
				must "not (../mac = '00:00:00:00:00:00') " +
				     "and not (substring(../mac, 2, 1) = '1')" +
				     "and not (substring(../mac, 2, 1) = '3')" +
				     "and not (substring(../mac, 2, 1) = '5')" +
				     "and not (substring(../mac, 2, 1) = '7')" +
				     "and not (substring(../mac, 2, 1) = '9')" +
				     "and not (substring(../mac, 2, 1) = 'b')" +
				     "and not (substring(../mac, 2, 1) = 'd')" +
				     "and not (substring(../mac, 2, 1) = 'f')" {
					error-message "MAC address must not be broadcast or multicast";
				}
				description "Used to match this interface based on the vendor MAC address assigned to a PCI device";
				configd:help "Vendor assigned MAC address";
			}
			leaf pci-address {
				type string {
					pattern '([0-9a-f]{1,4}:)?[0-9a-f]{1,2}:[01]?[0-9a-f].[0-7]' {
						error-message "Must have format as [<domain>:]<bus>:<slot>.<function>, where domain is 0-ffff, bus is 0-ff, slot is 0-1f and function 0-7";
					}
				}
				description "Used to match this interface to a specific PCI device by PCI address";
				configd:help "PCI hardware address";
			}
			leaf pci-slot {
				type uint32;
				description "Used to match this interface to a PCI device in specific PCI slot";
				configd:help "PCI slot";
			}
			leaf port {
				type uint32 {
					range "0..31";
				}
				description "Used to match this interface to a PCI device based on the discovery order used by DPDK";
				configd:help "Discovery order from DPDK";
			}
			leaf pci-function {
				type uint32 {
					range "0..7";
				}
				must "../pci-slot" {
					error-message "pci-function only valid with 'pci-slot'";
				}
				configd:help "Optional qualifier used when a PCI device has multiple functions";
				description "PCI function";
			}
			leaf dev-port {
				type uint32;
				must "../pci-address or ../pci-slot" {
					error-message "dev-port only valid with 'pci-address' or 'pci-slot'";
				}
				configd:help "Optional qualifier used when a PCI device has multiple ports";
				description "Device port on PCI device";
			}
		}
	}
}
