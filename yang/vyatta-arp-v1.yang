module vyatta-arp-v1 {
	namespace "urn:vyatta.com:mgmt:vyatta-arp:1";
	prefix  vyatta-arp-v1;

	import configd-v1 {
		prefix configd;
	}

	import vyatta-types-v1 {
		prefix types;
	}
	organization "AT&T Inc.";
	contact
		"AT&T
		 Postal: 208 S. Akard Street
		         Dallas, TX 75202.
		         USA
		 Web: www.att.com";

	description
		"Copyright (c) 2021, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Retrieves Address Resolution Protocol (ARP) data";

	revision 2021-09-15 {
		description "Added Neighbor Unreachability Detection state";
	}
	revision 2021-06-14 {
		description "Initial version";
	}

   rpc get-arp {
        description "Retrieve dataplane or control-plane ARP entries";

        configd:call-rpc "vyatta-op-arp";

        input {
            leaf source {
                description "Source of ARP entries";
                mandatory true;
                type enumeration {
                    enum dataplane {
                        description "Dataplane ARP entries";
                    }
                    enum control-plane {
                        description "Control-plane ARP entries";
                    }
                }
            }
            leaf ifname {
                description "Name of the interface";
                type types:interface-ifname;
            }
            leaf ip {
                description "IPv4 address";
                type types:ipv4-address;
            }
        }
        
        output {
            list arp-entry-list {
                key ip;
                description "List of ARP entries";
                leaf ip {
                        type types:ipv4-address;
                        description "IPv4 address";
                }
                leaf hwaddr {
                        mandatory true;
                        type types:mac-address;
                        description "MAC address to translate to";
                }
                leaf ifname {
                        mandatory true;
                        type types:interface-ifname;
                        description "Outgoing interface name";
                }               
                leaf flags {
                    type string;
                    description "Flags indicating the status of the arp entry";
                }
                leaf state {
                    description "ARP Neighbor Unreachability Detection state";
                    type string;
                }
                leaf platform_state {
                    type string;
                    description "Platform state";
                }
            }
        }
    }
}
