module vyatta-op-monitor-interfaces-dataplane-traffic-v1 {
	namespace "urn:vyatta.com:mgmt:vyatta-op-monitor-interfaces-dataplane-traffic:1";
	prefix vyatta-op-monitor-interfaces-dataplane-traffic-v1;

	import vyatta-opd-extensions-v1 {
		prefix opd;
	}
	import vyatta-op-monitor-v1 {
		prefix monitor;
	}
	import vyatta-op-monitor-interfaces-v1 {
		prefix monitor-if;
	}
	import vyatta-op-monitor-interfaces-dataplane-v1 {
		prefix monitor-if-dp;
	}

	organization "AT&T Inc.";
	contact
		"AT&T
		 Postal: 208 S. Akard Street
		         Dallas, TX 75202
		 Web: www.att.com";

	description
		"Copyright (c) 2020, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		Defines the 'monitor interfaces dataplane <if> traffic'
		operational CLI.";

	revision 2020-02-24 {
		description "Add support for hardware packet capture";
	}

	revision 2020-01-06 {
		description "Initial version";
	}

	feature monitor-platform-interface {
		description "Support for hardware packet capture";
	}

	opd:augment /monitor:monitor/monitor-if:interfaces/monitor-if-dp:dataplane/monitor-if-dp:ifname {
		opd:command traffic {
			opd:help "Monitor captured traffic on specified dataplane interface";
			opd:repeatable true;
			opd:inherit "monitor traffic options" {
				opd:on-enter 'vyatta-tshark.pl --intf $4 "${@:6}"';
			}

			opd:argument options {
				type enumeration {
					enum detail {
						opd:help "Dissect and display details of the captured traffic";
					}
					enum unlimited {
						opd:help "Continuously monitor captured traffic";
					}
				}
			}

			opd:option capture-size {
				opd:help "The number of bytes to capture from each frame";
				type uint32 {
					range 1..262144;
				}
			}

			opd:option filter {
				opd:help "Monitor filtered traffic for the specified dataplane interface";
				type string {
					opd:pattern-help "<capture-filter>";
					opd:help "Standard TSHARK packet filter string";
				}
			}

			opd:option bandwidth {
				if-feature monitor-platform-interface;
				opd:help "Backplane bandwidth, in kilobits-per-second, allocated to copied frames";
				type uint32 {
					range 20..1000000;
				}
				units "Kbits/sec";
			}

			opd:command software-only {
				if-feature monitor-platform-interface;
				opd:help "Turn off hardware packet capture";
			}

			opd:option save {
				opd:help "Save monitored traffic to a file";
				type string {
					opd:pattern-help "<name>.pcap";
					opd:help "Save monitored traffic to the specified file";
				}
				opd:inherit "" {
					opd:on-enter 'vyatta-tshark.pl --intf $4 "${@:6}"';
				}

				opd:option size {
					opd:help "Save monitored traffic to a file with max size";
					type string {
						opd:pattern-help "<number>";
						opd:help "Maximum file size (e.g., 1 = 1 KiB, 1M = 1 MiB)";
					}

					opd:option files {
						opd:help "Save monitored traffic to a set of rotated files";
						type string {
							opd:pattern-help "<number>";
							opd:help "Number of files to rotate stored traffic through";
						}
					}
				}
			}
		}
	}
}
